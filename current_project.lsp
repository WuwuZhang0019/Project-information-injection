;; 自动生成的CAD注入脚本
(setq xmmc "淄博周村吾悦广场西地块建设项目二期（地块三）")
(setq jsdw "淄博新城鸿拓房地产开发有限公司")
(setq zxmc "5#楼")
(setq xmbh "-5#")
(setq ctrq "2026-03")
(setq BBH "1.0")
(command "REGEN")
(princ "\n[淄博 / 5#楼] 变量已更新并自动刷新图纸。")
(princ)
