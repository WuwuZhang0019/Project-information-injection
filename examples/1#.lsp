;将此文件直接拖入cad即可。
(COMMAND "field")
(setq xmmc "津武（挂）2023-017号地块居住项目（三期）")
(setq jsdw "天津万新澜城置业有限公司")
(setq zxmc "1#楼")
(setq xmbh "STG2023422-	1#")
(setq ctrq "2025-01")
(setq BBH "B")
(COMMAND "REGEN")
(princ)
